FME workspace proj_zad3.fmw

Parameters:
- SourceDataset_SHAPEFILE = $(FME_MF_DIR)BazyDanychPrzestrzennych\ćwiczenia7\bdline_essh_gb\Data\GB\scotland_and_wales_region.shp   # Source Esri Shapefile(s)
- SourceDataset_GEOTIFF = ""$(FME_MF_DIR)BazyDanychPrzestrzennych\ćwiczenia7\ras250_gb\ras250_gb\data\HP.tif" "$(FME_MF_DIR)BazyDanychPrzestrzennych\ćwiczenia7\ras250_gb\ras250_gb\data\HT.tif" "$(FME_MF_DIR)BazyDanychPrzestrzennych\ćwiczenia7\ras250_gb\ras250_gb\data\HU.tif" "$(FME_MF_DIR)BazyDanychPrzestrzennych\ćwiczenia7\ras250_gb\ras250_gb\data\HW.tif" "$(FME_MF_DIR)BazyDanychPrzestrzennych\ćwiczenia7\ras250_gb\ras250_gb\data\HX.tif" "$(FME_MF_DIR)BazyDanychPrzestrzennych\ćwiczenia7\ras250_gb\ras250_gb\data\HY.tif" "$(FME_MF_DIR)BazyDanychPrzestrzennych\ćwiczenia7\ras250_gb\ras250_gb\data\HZ.tif" "$(FME_MF_DIR)BazyDanychPrzestrzennych\ćwiczenia7\ras250_gb\ras250_gb\data\NA.tif" "$(FME_MF_DIR)BazyDanychPrzestrzennych\ćwiczenia7\ras250_gb\ras250_gb\data\NB.tif" "$(FME_MF_DIR)BazyDanychPrzestrzennych\ćwiczenia7\ras250_gb\ras250_gb\data\NC.tif" "$(FME_MF_DIR)BazyDanychPrzestrzennych\ćwiczenia7\ras250_gb\ras250_gb\data\ND.tif" "$(FME_MF_DIR)BazyDanychPrzestrzennych\ćwiczenia7\ras250_gb\ras250_gb\data\NF.tif" "$(FME_MF_DIR)BazyDanychPrzestrzennych\ćwiczenia7\ras250_gb\ras250_gb\data\NG.tif" "$(FME_MF_DIR)BazyDanychPrzestrzennych\ćwiczenia7\ras250_gb\ras250_gb\data\NH.tif" "$(FME_MF_DIR)BazyDanychPrzestrzennych\ćwiczenia7\ras250_gb\ras250_gb\data\NJ.tif" "$(FME_MF_DIR)BazyDanychPrzestrzennych\ćwiczenia7\ras250_gb\ras250_gb\data\NK.tif" "$(FME_MF_DIR)BazyDanychPrzestrzennych\ćwiczenia7\ras250_gb\ras250_gb\data\NL.tif" "$(FME_MF_DIR)BazyDanychPrzestrzennych\ćwiczenia7\ras250_gb\ras250_gb\data\NM.tif" "$(FME_MF_DIR)BazyDanychPrzestrzennych\ćwiczenia7\ras250_gb\ras250_gb\data\NN.tif" "$(FME_MF_DIR)BazyDanychPrzestrzennych\ćwiczenia7\ras250_gb\ras250_gb\data\NO.tif" "$(FME_MF_DIR)BazyDanychPrzestrzennych\ćwiczenia7\ras250_gb\ras250_gb\data\NR.tif" "$(FME_MF_DIR)BazyDanychPrzestrzennych\ćwiczenia7\ras250_gb\ras250_gb\data\NS.tif" "$(FME_MF_DIR)BazyDanychPrzestrzennych\ćwiczenia7\ras250_gb\ras250_gb\data\NT.tif" "$(FME_MF_DIR)BazyDanychPrzestrzennych\ćwiczenia7\ras250_gb\ras250_gb\data\NU.tif" "$(FME_MF_DIR)BazyDanychPrzestrzennych\ćwiczenia7\ras250_gb\ras250_gb\data\NW.tif" "$(FME_MF_DIR)BazyDanychPrzestrzennych\ćwiczenia7\ras250_gb\ras250_gb\data\NX.tif" "$(FME_MF_DIR)BazyDanychPrzestrzennych\ćwiczenia7\ras250_gb\ras250_gb\data\NY.tif" "$(FME_MF_DIR)BazyDanychPrzestrzennych\ćwiczenia7\ras250_gb\ras250_gb\data\NZ.tif" "$(FME_MF_DIR)BazyDanychPrzestrzennych\ćwiczenia7\ras250_gb\ras250_gb\data\OV.tif" "$(FME_MF_DIR)BazyDanychPrzestrzennych\ćwiczenia7\ras250_gb\ras250_gb\data\SC.tif" "$(FME_MF_DIR)BazyDanychPrzestrzennych\ćwiczenia7\ras250_gb\ras250_gb\data\SD.tif" "$(FME_MF_DIR)BazyDanychPrzestrzennych\ćwiczenia7\ras250_gb\ras250_gb\data\SE.tif" "$(FME_MF_DIR)BazyDanychPrzestrzennych\ćwiczenia7\ras250_gb\ras250_gb\data\SH.tif" "$(FME_MF_DIR)BazyDanychPrzestrzennych\ćwiczenia7\ras250_gb\ras250_gb\data\SJ.tif" "$(FME_MF_DIR)BazyDanychPrzestrzennych\ćwiczenia7\ras250_gb\ras250_gb\data\SK.tif" "$(FME_MF_DIR)BazyDanychPrzestrzennych\ćwiczenia7\ras250_gb\ras250_gb\data\SM.tif" "$(FME_MF_DIR)BazyDanychPrzestrzennych\ćwiczenia7\ras250_gb\ras250_gb\data\SN.tif" "$(FME_MF_DIR)BazyDanychPrzestrzennych\ćwiczenia7\ras250_gb\ras250_gb\data\SO.tif" "$(FME_MF_DIR)BazyDanychPrzestrzennych\ćwiczenia7\ras250_gb\ras250_gb\data\SP.tif" "$(FME_MF_DIR)BazyDanychPrzestrzennych\ćwiczenia7\ras250_gb\ras250_gb\data\SR.tif" "$(FME_MF_DIR)BazyDanychPrzestrzennych\ćwiczenia7\ras250_gb\ras250_gb\data\SS.tif" "$(FME_MF_DIR)BazyDanychPrzestrzennych\ćwiczenia7\ras250_gb\ras250_gb\data\ST.tif" "$(FME_MF_DIR)BazyDanychPrzestrzennych\ćwiczenia7\ras250_gb\ras250_gb\data\SU.tif" "$(FME_MF_DIR)BazyDanychPrzestrzennych\ćwiczenia7\ras250_gb\ras250_gb\data\SV.tif" "$(FME_MF_DIR)BazyDanychPrzestrzennych\ćwiczenia7\ras250_gb\ras250_gb\data\SW.tif" "$(FME_MF_DIR)BazyDanychPrzestrzennych\ćwiczenia7\ras250_gb\ras250_gb\data\SX.tif" "$(FME_MF_DIR)BazyDanychPrzestrzennych\ćwiczenia7\ras250_gb\ras250_gb\data\SY.tif" "$(FME_MF_DIR)BazyDanychPrzestrzennych\ćwiczenia7\ras250_gb\ras250_gb\data\SZ.tif" "$(FME_MF_DIR)BazyDanychPrzestrzennych\ćwiczenia7\ras250_gb\ras250_gb\data\TA.tif" "$(FME_MF_DIR)BazyDanychPrzestrzennych\ćwiczenia7\ras250_gb\ras250_gb\data\TF.tif" "$(FME_MF_DIR)BazyDanychPrzestrzennych\ćwiczenia7\ras250_gb\ras250_gb\data\TG.tif" "$(FME_MF_DIR)BazyDanychPrzestrzennych\ćwiczenia7\ras250_gb\ras250_gb\data\TL.tif" "$(FME_MF_DIR)BazyDanychPrzestrzennych\ćwiczenia7\ras250_gb\ras250_gb\data\TM.tif" "$(FME_MF_DIR)BazyDanychPrzestrzennych\ćwiczenia7\ras250_gb\ras250_gb\data\TQ.tif" "$(FME_MF_DIR)BazyDanychPrzestrzennych\ćwiczenia7\ras250_gb\ras250_gb\data\TR.tif" "$(FME_MF_DIR)BazyDanychPrzestrzennych\ćwiczenia7\ras250_gb\ras250_gb\data\TV.tif""   # Source GeoTIFF File(s) or URL(s)
- DestDataset_POSTGIS_RASTER = new   # Connection
- DestDataset_POSTGRES = NewConnection   # Connection

Readers:
- SHAPEFILE_1: SHAPEFILE from $(SourceDataset_SHAPEFILE)
- GEOTIFF_1: GEOTIFF from $(SourceDataset_GEOTIFF)

Writers:
- POSTGIS_RASTER_1: POSTGIS_RASTER to $(DestDataset_POSTGIS_RASTER)
- POSTGRES_1: POSTGRES to $(DestDataset_POSTGRES)

scotland_and_wales_region (reader SHAPEFILE_1)
    attributes: NAME varchar(100), AREA_CODE varchar(3), DESCRIPTIO varchar(50), FILE_NAME varchar(100), NUMBER number(11,0), NUMBER0 number(11,0), POLYGON_ID number(11,0), UNIT_ID number(11,0), CODE varchar(9), HECTARES float, AREA float, TYPE_CODE varchar(2), DESCRIPT0 varchar(25), TYPE_COD0 varchar(3), DESCRIPT1 varchar(36)
    -> Tester
Tester
    BOOL_OP = OR
    TEST_CLAUSE = CASE_INSENSITIVE_TEST @Value(NAME) BEGINS_WITH South Wales
    TEST_MODE = CASE_INSENSITIVE_TEST
    PASSED -> Aggregator
Aggregator
    ACCUM_ATTRS_NAME = Use Attributes From One Feature
    AGGREGATE_TYPE = Homogeneous Collection (If Possible)
    MODE = Geometry - Assemble One Level
    SEP = ,
    AGGREGATE -> Clipper [CLIPPER]
GEOTIFF (reader GEOTIFF_1)
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> RasterPaletteResolver
RasterPaletteResolver
    -> Exports (writer POSTGRES_1)
Exports (writer POSTGRES_1)
